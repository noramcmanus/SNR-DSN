# FAA_Firefighting_Amphibious_Requirements

## FAA_Firefighting_Amphibious_Requirements!FAA_Requirements: References to FAA_Firefighting_Amphibious_Requirements.xlsx (FAA_Requirements) (Container)
Read-only references to Microsoft Excel document.
- srcFileChecksum: D02F80F2BEF4D4E9434729687A41CABB

### FAA-21-001: Restricted Category Type Certificate – Special Purpose (Functional)
Applicant must obtain a Restricted Category Type Certificate under 14 CFR §21.25 for aerial dispensing of firefighting materials (forest and wildlife conservation). No feature or characteristic may make the aircraft unsafe when operated under limitations prescribed for its intended use.

### FAA-21-002: Special Purpose Operation – Aerial Firefighting (Functional)
The restricted category certificate must specifically list aerial dispensing of firefighting materials under §21.25(b)(2)(i) (forest and wildlife conservation).

### FAA-21-003: Compliance with Applicable Airworthiness Requirements (Functional)
Aircraft must meet the airworthiness requirements of an applicable category (Part 23 or Part 25) except those the FAA finds inappropriate for the special purpose operation.

### FAA-21-004: Noise Compliance (Functional)
Applicant must show compliance with applicable noise requirements of 14 CFR Part 36.

### FAA-21-005: Instructions for Continued Airworthiness (ICA) (Functional)
FAA-approved Instructions for Continued Airworthiness must be prepared for both the baseline aircraft and the firefighting (airtanker) mission configuration, meeting §25.1529 / §23.1529 as applicable at Amendment 54 or later.

### FAA-STR-001: Fatigue and Damage Tolerance Evaluation – Firefighting Mission (Functional)
A fatigue and damage tolerance evaluation per §25.571 (Amdt. 25-54 or later) must identify loads, internal and external, to which principal structural elements (PSEs) are subjected in the firefighting role, and determine the impact of those loads on structural integrity.

### FAA-STR-002: FAA Form 8110-3 – Fatigue Compliance Statement (Functional)
Documentation must include an FAA Form 8110-3 (Statement of Compliance with FARs) specifying in the Purpose of Data block: 'Fatigue and Damage Tolerance evaluations for the aerial dispersion mission usage' and referencing §25.571 Amdt. 25-54 or later.

### FAA-AMP-001: Hull Buoyancy Requirements (Functional)
The hull must provide buoyancy 80% in excess of that required to support the maximum weight of the airplane in fresh water.

### FAA-AMP-002: Hull Stability – No Capsize in Calm Water (Functional)
The aircraft must have sufficient margin to stay afloat at rest in calm water without capsizing in case of a likely float or hull flooding.

### FAA-AMP-003: Hull and Main Float Load Factors (Functional)
Structural load factors for the hull and main floats must be determined per §23.527 covering water landing conditions, step-turn, and planing conditions.

### FAA-AMP-004: Hull and Main Float Landing Conditions (Functional)
Design must account for hull landing conditions per §23.529, including symmetrical step landing, symmetrical bow-and-stern landing, and unsymmetrical landing.

### FAA-AMP-005: Hull Takeoff Condition (Functional)
Design must address hull takeoff loads per §23.531 accounting for spray loads and hydrodynamic lift during water takeoff acceleration.

### FAA-AMP-006: Hull Bottom Pressures (Functional)
Hull bottom pressure distribution must be determined per §23.533 for the design water load conditions.

### FAA-AMP-007: Auxiliary Float Loads (Functional)
Auxiliary float structural loads must be determined per §23.535.

### FAA-AMP-008: Seaplane Riding Lights (Functional)
Riding lights must provide a white light visible in clear atmospheric conditions for seaplane/amphibian aircraft.

### FAA-AMP-009: Water Rudder / Directional Control on Water (Functional)
Means for directional control while taxiing on water must be provided; water rudder systems must be shown adequate for all required water maneuvers.

### FAA-AMP-010: Seaplane Appendix I – Loads (Functional)
All applicable seaplane load criteria in Appendix I to Part 23 must be addressed in the structural analysis.

### FAA-PP-001: Engine Type Certificate – Turboprop (Functional)
Each turboprop engine must be type certificated per 14 CFR Part 33 (Airworthiness Standards: Aircraft Engines).

### FAA-PP-002: Propeller Type Certificate (Functional)
Each propeller must be type certificated per 14 CFR Part 35 (Airworthiness Standards: Propellers).

### FAA-PP-003: Engine Installation – Turboprop Compliance (Functional)
Turboprop installations must comply with Part 23 Subpart E powerplant requirements, including engine controls, fuel system, oil system, cooling, and fire protection.

### FAA-PP-004: Engine Cooling – Low-Speed / Scooping Flight Regime (Functional)
Engine cooling must be shown adequate throughout the operating envelope including low-altitude, low-speed flight during water scooping and fire drop operations.

### FAA-PP-005: Engine Fire Protection (Functional)
Each engine must be isolated in a fire zone with firewall, drain provisions, and fire detection system. Turboprop installations require flammable fluid shut-off means.

### FAA-PP-006: Propeller Clearance (Functional)
Propeller clearance from ground and water must meet minimum clearance requirements per §23.925. Must account for amphibious operations and trim at scooping attitude.

### FAA-PP-007: Engine Ice Protection (Functional)
Engine induction system ice protection must be provided and demonstrated effective throughout the required flight envelope.

### FAA-PP-008: One Engine Inoperative (OEI) Performance (Functional)
Aircraft must demonstrate climb performance with one engine inoperative at the appropriate certification level, including at the maximum scooping/dispensing weight.

### FAA-FF-001: Retardant/Water Tank System Design (Functional)
The onboard water/retardant tank and dispensing system must be designed and installed as a certified modification (STC or TC change). System must not adversely affect flight characteristics, structural integrity, or any aircraft system.

### FAA-FF-002: Drop Door / Dispensing System – Structural Loads (Functional)
Structural loads imparted by the water/retardant dispensing system (fill, carry, drop) must be evaluated and shown not to exceed design limit loads for the airframe.

### FAA-FF-003: Scooping System Intake – Hydrodynamic and Structural (Functional)
The water intake scoop system must be structurally evaluated for hydrodynamic drag loads during scooping at approved scoop speeds and sea states.

### FAA-FF-004: Retardant Chemical Compatibility (Functional)
All materials in the tank, dispensing system, and potentially exposed airframe areas must be shown compatible with fire retardant chemicals used in the mission (ammonium polyphosphate-based retardants and water).

### FAA-FF-005: Flight Manual Supplement – Firefighting Operations (Functional)
An FAA-approved Airplane Flight Manual Supplement (AFMS) must be prepared covering the firefighting mission, including scooping speeds, drop speeds, system operating procedures, emergency procedures, and performance data.

### FAA-FF-006: Placards and Markings – Mission Equipment (Functional)
All mission-specific controls (tank, scoop, drop doors) must be labeled with appropriate placards per §23.1555 and §23.1557.

### FAA-OPS-001: Airworthiness Certificate – Restricted Category (Functional)
Aircraft must hold a current and valid restricted category airworthiness certificate issued per §21.183 / §21.185 and displayed per §91.203.

### FAA-OPS-002: Operational Limitations – Restricted Category (Functional)
The aircraft must be operated in accordance with the limitations of its restricted category certificate. Operations over populated areas and in congested airways require FAA waiver per §91.313.

### FAA-OPS-003: Annual / Periodic Inspection (Functional)
Turbopropeller-powered multiengine airplanes must operate under an FAA-approved inspection program per §91.409(e), rather than a standard annual inspection.

### FAA-OPS-004: Fuel Venting and Exhaust Emissions (Functional)
Aircraft must comply with fuel venting and exhaust emission requirements of 14 CFR Part 34.
