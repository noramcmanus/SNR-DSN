# aoe4066_team6_main

## 1: Maximum Takeoff Mass (Functional)
The takeoff mass of each plane should not exceed 25,000 kg.

## 2: Maximum Payload Mass (Functional)
Each payload should not exceed 10,000 kg.

## 3: Targeted Entry Year (Functional)
The fleet should be ready for service by the year 2035.

## 4: Budget (Functional)
The overall budget of the fleet shall not exceed 100 million euros.

## 5: FAA Requirements (Functional)
Must meet Title 14 Chapter 1 Subchapter C Part 25 Requirements.

## 6: Fire Detection (Functional)
Must be able to detect fires and risk areas.

## 7: Fire Suppression (Functional)
Must be able to put out fires and prevent spread to risk areas.

## 8: Takeoff Distance (Functional)
The fleet should be able to takeoff from less than 2500 feet.

## 9: Response Time (Functional)
Fleet shall be able to respond to a threat in no more than two hours.

## 10: Service Ceiling (Functional)
Service ceiling for the fleet must be at least 14,000 feet.

## 11: Temperature (Functional)
Fleet must have the ability to sustain heats of approximately 250*F.

## 12: Corrosion Resistance (Functional)
Any surfaces typically in contact with water must be resistant to corrosion.

## 13: Engine (Functional)
Aircraft shall use a TRL 9 engine.

## 14: Scooping (Functional)
Aircraft shall be able to refill water supply from existing water sources.

### 18: Amphibious (Functional)
Aircraft shall be able to takeoff and land on water.

#### 34: Waterproof (Functional)
Aircraft shall be water tight in places water could cause damage.

### 23: Water Depth (Functional)
Aircraft should operate with a minimum water depth of 5 feet.

### 27: Water Refill Time (Functional)
When on water, tank should refill in less than 30 seconds.

### 39: Overfill Protection (Functional)
Aircraft shall not be able to exceed its MTOW due to overfilling.

## 15: Range (Functional)
Aircraft should have the ability to fly a distance of 1,300 nm without refueling.

## 16: Coverage Area (Functional)
Aircraft's payload should cover () square feet of forest before refilling.

## 17: Capacity (Functional)
Aircraft should hold at least 1,500 gallons of water.

## 19: STOL (Functional)
Aircraft shall be capable of short takeoff and landing.

## 20: High Lift (Functional)
Aircraft shall have high lifting wings for short takeoff and landing.

## 21: Stall Speed (Functional)
Aircraft shall have a stall speed of no more than 60 kts at MTOW.

## 22: Propulstion Type (Functional)
Aircraft should be operated using a propellor.

## 24: Pilot Visibility (Functional)
The pilot should have 240 degrees of visibility.

## 25: Wave Height (Functional)
The aircraft shall sustain waves of 6 feet in height.

## 26: Land Refill Time (Functional)
When on land, tank should refill in less than 5 minutes.

## 28: Fuel Efficiency (Functional)
The engine picked shall have high fuel efficiency.

## 29: Climb Rate (Functional)
The aircraft shall have a climb rate of 1000 ft/min.

## 30: Thrust/Weight Ratio (Functional)
Should have a high thrust/weight ratio.

## 31: Maximum Weight Factor (Functional)
Shall sustain weight factors of up to 4 g's.

## 32: Payload Drop (Functional)
Should have the ability to drop it's payload both all at once and dispersed over an area.

## 33: Engine Out (Functional)
Vertical stabilizer shall compensate for thrust moment imbalance from one engine out.

## 35: Floatation Devices (Functional)
Aircraft shall have floatation on board incase of emergency water landing.

## 36: Search and Rescue (Functional)
Aircraft should be search and rescue capable.

## 37: Lights (Functional)
Aircraft shalll have exterior lights in accordance to the FAA requirements.

## 38: Air Conditioning (Functional)
Aircraft shall have A/C due to high temperature environment.

## 40: Payload Targetting (Functional)
Aircraft should use systems to accurately target and drop its payload.

## 41: Mechanical Downtime (Functional)
Aircraft should use predicitive maintenance to avoid excess mechanical downtime.

## 42: Interfleet Communication (Functional)
Aircraft shall have the ability to communicate with other vehicles within the fleet.

## 43: Color (Functional)
Aircraft shall be highly visible in both night and day conditions.

## 44: Bilge Pump (Functional)
Aircraft shall be able to remove excess water.

## 45: Max Landing Vertical Speed (Functional)
Aircraft shall sustain vertical landing velocity of 10 ft/s.

## 46: Impact Resistance (Functional)
Aircraft shall sustain water impacts from scooping.

## 47: Ash/Smoke Ingestion (Functional)
Engine shall still be able to work in areas of high ash/smoke concentration.

## 48: Water Ingestion (Functional)
Engine shall still be able to work despite ocean/payload spray.

## 49: Scooping Friction (Functional)
Aircraft shall sustain sudden increases in frictional forces/moments while scooping water.
